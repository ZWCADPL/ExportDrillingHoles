(command "_netload" "F:/____Szansa/_____Visual Studio 2010/Functionalities/DrillingHoles/DrillingHoles/bin/Debug/DrillingHoles.dll")

; (command "_ZOOM" "_W" "266910.61,529581.21" "271714.23,535134.72" )
